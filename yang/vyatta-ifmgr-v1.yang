module vyatta-ifmgr-v1 {
	namespace "urn:vyatta.com:mgmt:vyatta-ifmgr:1";
	prefix vyatta-ifmgr-v1;

        organization "AT&T Inc.";
        contact
                "AT&T
                 Postal: 208 S. Akard Street
                         Dallas, TX 75202
                 Web: www.att.com";

	description
		"Copyright (c) 2018-2019, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for the interface manager.";

	revision 2018-01-04 {
		description "Intial revision";
	}

	notification configuration-updated {
		description "Notifies that the running configuration of an interface has been updated";

		container interface {
			description "Interface's identifying information";
			leaf name {
				description "Interface name";
				mandatory true;
				type string;
			}
		}
	}

	notification interface-state {
		description "Notification that an interface has changed state. State changes " +
			"can be in response to system plug/unplug events, configuration changes " +
			"or other system events.";
		container interface {
			description "Interface's identifying information";
			leaf name {
				description "Interface name";
				mandatory true;
				type string;
			}
			leaf state {
				description "Indicates if the interface is plugged in or not." +
					"plug - last plug/unplug system notification was plug." +
					"unplug - last plug/unplug system notification was unplug";
				mandatory true;
				type enumeration {
					enum "unknown" {
						description "The current state of the interface is unknown";
					}
					enum "unplugged" {
						description "An unplug event has been observed for the interface";
					}
					enum "plugged" {
						description "A plug event has been observed for the interface";
					}
				}
			}
		}
	}
}
