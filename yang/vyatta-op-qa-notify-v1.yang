module vyatta-op-qa-notify-v1 {
	namespace "urn:net.vyatta.eng:service:vyatta-op-qa-notify:1";
	prefix vyatta-op-qa-notify-v1;

	import vyatta-opd-extensions-v1 {
		prefix opd;
	}

	organization "AT&T Inc.";
	contact
		"AT&T
		 Postal: 208 S. Akard Street
		         Dallas, TX 75202
		 Web: www.att.com";

	description
		"Copyright (c) 2018-2019 AT&T Intellectual Property
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Experimental QA Notify commands
		 These are experimental commands that may be
		 changed/removed without any notice";

	revision 2018-01-04 {
		description "Initial revision.";
	}

	grouping set-delete {
		opd:option set {
			description "A path that must be present in the configuration
				for the command to return success";
			opd:help "Configuration that must be set";
			type string;
		}

		opd:option delete {
			description "A configuration path that must not be present in
				in the configuration for the command to return success";
			opd:help "Configuration that must not be set";
			type string;
		}

		opd:argument interface-name {
			description "An interface name";
			opd:help "Interface name";
			type string;
		}
	}

	opd:command qa-notify {
		opd:help "QA notification";
		status obsolete;

		opd:command wait {
			opd:help "Wait for component to change to desired state";

			opd:command ifmgr {
				description "Interface manager component";
				opd:help "Interface Manager";
				opd:repeatable true;
				opd:on-enter "";
				opd:inherit "" {
					opd:privileged true;
					opd:on-enter 'qa-notify "${@:4}"';
				}

				uses set-delete;
				opd:option timeout {
					description "Wait for the specified time for the configuration
						to match the desired state. If not acheived when the
						timeout expires, the command will return success";
					opd:help "Maximum time to wait in seconds";
					type uint32 {
						range 1..600;
					}
				}
			}
		}
	}
}
